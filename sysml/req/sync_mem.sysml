// SPDX-FileCopyrightText: 2026 Kari Vierimaa, Kempele, Finland
// SPDX-License-Identifier: Apache-2.0
//
// Ancillary repository file (not Covered Source). RTL is under Apache-2.0; see NOTICE.

package PoC_Requirements_SyncMem {
    doc /*
     * Requirement stubs for sync and ocram modules. SHALL prose lives only in docs/modules.
     */

    private import ScalarValues::*;
    private import ArchitectureMeta::*;

    @OKFReference {
        docPath = "docs/modules/sync/sync_Bits.md";
        conceptId = "modules/sync/sync_Bits";
        section = "REQ-sync_Bits-001";
    }
    requirement def <'REQ-sync_Bits-001'> REQ_sync_Bits_001 {
        doc /* OKF: docs/modules/sync/sync_Bits.md#REQ-sync_Bits-001 */
        require constraint { true == true }
    }

    @OKFReference {
        docPath = "docs/modules/sync/sync_Bits.md";
        conceptId = "modules/sync/sync_Bits";
        section = "REQ-sync_Bits-002";
    }
    requirement def <'REQ-sync_Bits-002'> REQ_sync_Bits_002 {
        doc /* OKF: docs/modules/sync/sync_Bits.md#REQ-sync_Bits-002 */
        require constraint { true == true }
    }

    @OKFReference {
        docPath = "docs/modules/sync/sync_Reset.md";
        conceptId = "modules/sync/sync_Reset";
        section = "REQ-sync_Reset-001";
    }
    requirement def <'REQ-sync_Reset-001'> REQ_sync_Reset_001 {
        doc /* OKF: docs/modules/sync/sync_Reset.md#REQ-sync_Reset-001 */
        require constraint { true == true }
    }

    @OKFReference {
        docPath = "docs/modules/sync/sync_Reset.md";
        conceptId = "modules/sync/sync_Reset";
        section = "REQ-sync_Reset-002";
    }
    requirement def <'REQ-sync_Reset-002'> REQ_sync_Reset_002 {
        doc /* OKF: docs/modules/sync/sync_Reset.md#REQ-sync_Reset-002 */
        require constraint { true == true }
    }

    @OKFReference {
        docPath = "docs/modules/sync/sync_Pulse.md";
        conceptId = "modules/sync/sync_Pulse";
        section = "REQ-sync_Pulse-001";
    }
    requirement def <'REQ-sync_Pulse-001'> REQ_sync_Pulse_001 {
        doc /* OKF: docs/modules/sync/sync_Pulse.md#REQ-sync_Pulse-001 */
        require constraint { true == true }
    }

    @OKFReference {
        docPath = "docs/modules/sync/sync_Strobe.md";
        conceptId = "modules/sync/sync_Strobe";
        section = "REQ-sync_Strobe-001";
    }
    requirement def <'REQ-sync_Strobe-001'> REQ_sync_Strobe_001 {
        doc /* OKF: docs/modules/sync/sync_Strobe.md#REQ-sync_Strobe-001 */
        require constraint { true == true }
    }

    @OKFReference {
        docPath = "docs/modules/sync/sync_Command.md";
        conceptId = "modules/sync/sync_Command";
        section = "REQ-sync_Command-001";
    }
    requirement def <'REQ-sync_Command-001'> REQ_sync_Command_001 {
        doc /* OKF: docs/modules/sync/sync_Command.md#REQ-sync_Command-001 */
        require constraint { true == true }
    }

    @OKFReference {
        docPath = "docs/modules/sync/sync_Vector.md";
        conceptId = "modules/sync/sync_Vector";
        section = "REQ-sync_Vector-001";
    }
    requirement def <'REQ-sync_Vector-001'> REQ_sync_Vector_001 {
        doc /* OKF: docs/modules/sync/sync_Vector.md#REQ-sync_Vector-001 */
        require constraint { true == true }
    }

    @OKFReference {
        docPath = "docs/modules/mem/ocram/ocram_SinglePort.md";
        conceptId = "modules/mem/ocram/ocram_SinglePort";
        section = "REQ-ocram_SinglePort-001";
    }
    requirement def <'REQ-ocram_SinglePort-001'> REQ_ocram_SinglePort_001 {
        doc /* OKF: docs/modules/mem/ocram/ocram_SinglePort.md#REQ-ocram_SinglePort-001 */
        require constraint { true == true }
    }

    @OKFReference {
        docPath = "docs/modules/mem/ocram/ocram_SimpleDualPort.md";
        conceptId = "modules/mem/ocram/ocram_SimpleDualPort";
        section = "REQ-ocram_SimpleDualPort-001";
    }
    requirement def <'REQ-ocram_SimpleDualPort-001'> REQ_ocram_SimpleDualPort_001 {
        doc /* OKF: docs/modules/mem/ocram/ocram_SimpleDualPort.md#REQ-ocram_SimpleDualPort-001 */
        require constraint { true == true }
    }

    @OKFReference {
        docPath = "docs/modules/mem/ocram/ocram_SimpleDualPort.md";
        conceptId = "modules/mem/ocram/ocram_SimpleDualPort";
        section = "REQ-ocram_SimpleDualPort-002";
    }
    requirement def <'REQ-ocram_SimpleDualPort-002'> REQ_ocram_SimpleDualPort_002 {
        doc /* OKF: docs/modules/mem/ocram/ocram_SimpleDualPort.md#REQ-ocram_SimpleDualPort-002 */
        require constraint { true == true }
    }

    @OKFReference {
        docPath = "docs/modules/mem/ocram/ocram_SimpleDualPort.md";
        conceptId = "modules/mem/ocram/ocram_SimpleDualPort";
        section = "REQ-ocram_SimpleDualPort-003";
    }
    requirement def <'REQ-ocram_SimpleDualPort-003'> REQ_ocram_SimpleDualPort_003 {
        doc /* OKF: docs/modules/mem/ocram/ocram_SimpleDualPort.md#REQ-ocram_SimpleDualPort-003 */
        require constraint { true == true }
    }

    @OKFReference {
        docPath = "docs/modules/mem/ocram/ocram_SimpleDualPort_Optimized.md";
        conceptId = "modules/mem/ocram/ocram_SimpleDualPort_Optimized";
        section = "REQ-ocram_SimpleDualPort_Optimized-001";
    }
    requirement def <'REQ-ocram_SimpleDualPort_Optimized-001'> REQ_ocram_SimpleDualPort_Optimized_001 {
        doc /* OKF: docs/modules/mem/ocram/ocram_SimpleDualPort_Optimized.md#REQ-ocram_SimpleDualPort_Optimized-001 */
        require constraint { true == true }
    }

    @OKFReference {
        docPath = "docs/modules/mem/ocram/ocram_SimpleDualPort_WriteFirst.md";
        conceptId = "modules/mem/ocram/ocram_SimpleDualPort_WriteFirst";
        section = "REQ-ocram_SimpleDualPort_WriteFirst-001";
    }
    requirement def <'REQ-ocram_SimpleDualPort_WriteFirst-001'> REQ_ocram_SimpleDualPort_WriteFirst_001 {
        doc /* OKF: docs/modules/mem/ocram/ocram_SimpleDualPort_WriteFirst.md#REQ-ocram_SimpleDualPort_WriteFirst-001 */
        require constraint { true == true }
    }

    @OKFReference {
        docPath = "docs/modules/mem/ocram/ocram_EnhancedSimpleDualPort.md";
        conceptId = "modules/mem/ocram/ocram_EnhancedSimpleDualPort";
        section = "REQ-ocram_EnhancedSimpleDualPort-001";
    }
    requirement def <'REQ-ocram_EnhancedSimpleDualPort-001'> REQ_ocram_EnhancedSimpleDualPort_001 {
        doc /* OKF: docs/modules/mem/ocram/ocram_EnhancedSimpleDualPort.md#REQ-ocram_EnhancedSimpleDualPort-001 */
        require constraint { true == true }
    }

    @OKFReference {
        docPath = "docs/modules/mem/ocram/ocram_TrueDualPort.md";
        conceptId = "modules/mem/ocram/ocram_TrueDualPort";
        section = "REQ-ocram_TrueDualPort-001";
    }
    requirement def <'REQ-ocram_TrueDualPort-001'> REQ_ocram_TrueDualPort_001 {
        doc /* OKF: docs/modules/mem/ocram/ocram_TrueDualPort.md#REQ-ocram_TrueDualPort-001 */
        require constraint { true == true }
    }

    @OKFReference {
        docPath = "docs/modules/mem/ocram/ocram_TrueDualPort_WriteFirst.md";
        conceptId = "modules/mem/ocram/ocram_TrueDualPort_WriteFirst";
        section = "REQ-ocram_TrueDualPort_WriteFirst-001";
    }
    requirement def <'REQ-ocram_TrueDualPort_WriteFirst-001'> REQ_ocram_TrueDualPort_WriteFirst_001 {
        doc /* OKF: docs/modules/mem/ocram/ocram_TrueDualPort_WriteFirst.md#REQ-ocram_TrueDualPort_WriteFirst-001 */
        require constraint { true == true }
    }

    @OKFReference {
        docPath = "docs/modules/mem/ocram/ocram_TrueDualPort_Simulation.md";
        conceptId = "modules/mem/ocram/ocram_TrueDualPort_Simulation";
        section = "REQ-ocram_TrueDualPort_Simulation-001";
    }
    requirement def <'REQ-ocram_TrueDualPort_Simulation-001'> REQ_ocram_TrueDualPort_Simulation_001 {
        doc /* OKF: docs/modules/mem/ocram/ocram_TrueDualPort_Simulation.md#REQ-ocram_TrueDualPort_Simulation-001 */
        require constraint { true == true }
    }
}
