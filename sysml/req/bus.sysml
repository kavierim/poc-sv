// SPDX-FileCopyrightText: 2026 Kari Vierimaa, Kempele, Finland
// SPDX-License-Identifier: Apache-2.0
//
// Ancillary repository file (not Covered Source).
// Requirement stubs. SHALL prose lives only in docs/modules.

package PoC_Requirements_Bus {
    doc /*
     * Bus-domain requirement stubs. SHALL prose lives only in docs/modules.
     */

    private import ScalarValues::*;
    private import ArchitectureMeta::*;

    requirement def <'REQ-axi4_AXI4Lite_Converter-001'> REQ_axi4_AXI4Lite_Converter_001 {
        doc /* OKF: docs/modules/bus/axi4/axi4_AXI4Lite_Converter.md#REQ-axi4_AXI4Lite_Converter-001 */
    }

    requirement def <'REQ-axi4_AXI4Lite_Converter-002'> REQ_axi4_AXI4Lite_Converter_002 {
        doc /* OKF: docs/modules/bus/axi4/axi4_AXI4Lite_Converter.md#REQ-axi4_AXI4Lite_Converter-002 */
    }

    requirement def <'REQ-axi4_DeMux-001'> REQ_axi4_DeMux_001 {
        doc /* OKF: docs/modules/bus/axi4/axi4_DeMux.md#REQ-axi4_DeMux-001 */
    }

    requirement def <'REQ-axi4_DeMux-002'> REQ_axi4_DeMux_002 {
        doc /* OKF: docs/modules/bus/axi4/axi4_DeMux.md#REQ-axi4_DeMux-002 */
    }

    requirement def <'REQ-axi4_DeMux-003'> REQ_axi4_DeMux_003 {
        doc /* OKF: docs/modules/bus/axi4/axi4_DeMux.md#REQ-axi4_DeMux-003 */
    }

    requirement def <'REQ-axi4_DeMux-004'> REQ_axi4_DeMux_004 {
        doc /* OKF: docs/modules/bus/axi4/axi4_DeMux.md#REQ-axi4_DeMux-004 */
    }

    requirement def <'REQ-axi4_DeMux-005'> REQ_axi4_DeMux_005 {
        doc /* OKF: docs/modules/bus/axi4/axi4_DeMux.md#REQ-axi4_DeMux-005 */
    }

    requirement def <'REQ-axi4_FIFO_CDC-001'> REQ_axi4_FIFO_CDC_001 {
        doc /* OKF: docs/modules/bus/axi4/axi4_FIFO_CDC.md#REQ-axi4_FIFO_CDC-001 */
    }

    requirement def <'REQ-axi4_FIFO_CDC-002'> REQ_axi4_FIFO_CDC_002 {
        doc /* OKF: docs/modules/bus/axi4/axi4_FIFO_CDC.md#REQ-axi4_FIFO_CDC-002 */
    }

    requirement def <'REQ-axi4_FIFO_CDC-003'> REQ_axi4_FIFO_CDC_003 {
        doc /* OKF: docs/modules/bus/axi4/axi4_FIFO_CDC.md#REQ-axi4_FIFO_CDC-003 */
    }

    requirement def <'REQ-axi4_FIFO_CDC-004'> REQ_axi4_FIFO_CDC_004 {
        doc /* OKF: docs/modules/bus/axi4/axi4_FIFO_CDC.md#REQ-axi4_FIFO_CDC-004 */
    }

    requirement def <'REQ-axi4_FIFO-001'> REQ_axi4_FIFO_001 {
        doc /* OKF: docs/modules/bus/axi4/axi4_FIFO.md#REQ-axi4_FIFO-001 */
    }

    requirement def <'REQ-axi4_FIFO-002'> REQ_axi4_FIFO_002 {
        doc /* OKF: docs/modules/bus/axi4/axi4_FIFO.md#REQ-axi4_FIFO-002 */
    }

    requirement def <'REQ-axi4_FIFO-003'> REQ_axi4_FIFO_003 {
        doc /* OKF: docs/modules/bus/axi4/axi4_FIFO.md#REQ-axi4_FIFO-003 */
    }

    requirement def <'REQ-axi4_Mux-001'> REQ_axi4_Mux_001 {
        doc /* OKF: docs/modules/bus/axi4/axi4_Mux.md#REQ-axi4_Mux-001 */
    }

    requirement def <'REQ-axi4_Mux-002'> REQ_axi4_Mux_002 {
        doc /* OKF: docs/modules/bus/axi4/axi4_Mux.md#REQ-axi4_Mux-002 */
    }

    requirement def <'REQ-axi4_Mux-003'> REQ_axi4_Mux_003 {
        doc /* OKF: docs/modules/bus/axi4/axi4_Mux.md#REQ-axi4_Mux-003 */
    }

    requirement def <'REQ-axi4_Sink-001'> REQ_axi4_Sink_001 {
        doc /* OKF: docs/modules/bus/axi4/axi4_Sink.md#REQ-axi4_Sink-001 */
    }

    requirement def <'REQ-axi4_Sink-002'> REQ_axi4_Sink_002 {
        doc /* OKF: docs/modules/bus/axi4/axi4_Sink.md#REQ-axi4_Sink-002 */
    }

    requirement def <'REQ-axi4_Termination_Manager-001'> REQ_axi4_Termination_Manager_001 {
        doc /* OKF: docs/modules/bus/axi4/axi4_Termination_Manager.md#REQ-axi4_Termination_Manager-001 */
    }

    requirement def <'REQ-axi4_Termination_Subordinate-001'> REQ_axi4_Termination_Subordinate_001 {
        doc /* OKF: docs/modules/bus/axi4/axi4_Termination_Subordinate.md#REQ-axi4_Termination_Subordinate-001 */
    }

    requirement def <'REQ-axi4lite_DeMux-001'> REQ_axi4lite_DeMux_001 {
        doc /* OKF: docs/modules/bus/axi4lite/axi4lite_DeMux.md#REQ-axi4lite_DeMux-001 */
    }

    requirement def <'REQ-axi4lite_DeMux-002'> REQ_axi4lite_DeMux_002 {
        doc /* OKF: docs/modules/bus/axi4lite/axi4lite_DeMux.md#REQ-axi4lite_DeMux-002 */
    }

    requirement def <'REQ-axi4lite_DeMux-003'> REQ_axi4lite_DeMux_003 {
        doc /* OKF: docs/modules/bus/axi4lite/axi4lite_DeMux.md#REQ-axi4lite_DeMux-003 */
    }

    requirement def <'REQ-axi4lite_DeMux-004'> REQ_axi4lite_DeMux_004 {
        doc /* OKF: docs/modules/bus/axi4lite/axi4lite_DeMux.md#REQ-axi4lite_DeMux-004 */
    }

    requirement def <'REQ-axi4lite_FIFO_CDC-001'> REQ_axi4lite_FIFO_CDC_001 {
        doc /* OKF: docs/modules/bus/axi4lite/axi4lite_FIFO_CDC.md#REQ-axi4lite_FIFO_CDC-001 */
    }

    requirement def <'REQ-axi4lite_FIFO_CDC-002'> REQ_axi4lite_FIFO_CDC_002 {
        doc /* OKF: docs/modules/bus/axi4lite/axi4lite_FIFO_CDC.md#REQ-axi4lite_FIFO_CDC-002 */
    }

    requirement def <'REQ-axi4lite_FIFO_CDC-003'> REQ_axi4lite_FIFO_CDC_003 {
        doc /* OKF: docs/modules/bus/axi4lite/axi4lite_FIFO_CDC.md#REQ-axi4lite_FIFO_CDC-003 */
    }

    requirement def <'REQ-axi4lite_FIFO_CDC-004'> REQ_axi4lite_FIFO_CDC_004 {
        doc /* OKF: docs/modules/bus/axi4lite/axi4lite_FIFO_CDC.md#REQ-axi4lite_FIFO_CDC-004 */
    }

    requirement def <'REQ-axi4lite_FIFO-001'> REQ_axi4lite_FIFO_001 {
        doc /* OKF: docs/modules/bus/axi4lite/axi4lite_FIFO.md#REQ-axi4lite_FIFO-001 */
    }

    requirement def <'REQ-axi4lite_FIFO-002'> REQ_axi4lite_FIFO_002 {
        doc /* OKF: docs/modules/bus/axi4lite/axi4lite_FIFO.md#REQ-axi4lite_FIFO-002 */
    }

    requirement def <'REQ-axi4lite_FIFO-003'> REQ_axi4lite_FIFO_003 {
        doc /* OKF: docs/modules/bus/axi4lite/axi4lite_FIFO.md#REQ-axi4lite_FIFO-003 */
    }

    requirement def <'REQ-axi4lite_OCRAM_Adapter-001'> REQ_axi4lite_OCRAM_Adapter_001 {
        doc /* OKF: docs/modules/bus/axi4lite/axi4lite_OCRAM_Adapter.md#REQ-axi4lite_OCRAM_Adapter-001 */
    }

    requirement def <'REQ-axi4lite_OCRAM_Adapter-002'> REQ_axi4lite_OCRAM_Adapter_002 {
        doc /* OKF: docs/modules/bus/axi4lite/axi4lite_OCRAM_Adapter.md#REQ-axi4lite_OCRAM_Adapter-002 */
    }

    requirement def <'REQ-axi4lite_Register-001'> REQ_axi4lite_Register_001 {
        doc /* OKF: docs/modules/bus/axi4lite/axi4lite_Register.md#REQ-axi4lite_Register-001 */
    }

    requirement def <'REQ-axi4lite_Register-002'> REQ_axi4lite_Register_002 {
        doc /* OKF: docs/modules/bus/axi4lite/axi4lite_Register.md#REQ-axi4lite_Register-002 */
    }

    requirement def <'REQ-axi4lite_Termination_Manager-001'> REQ_axi4lite_Termination_Manager_001 {
        doc /* OKF: docs/modules/bus/axi4lite/axi4lite_Termination_Manager.md#REQ-axi4lite_Termination_Manager-001 */
    }

    requirement def <'REQ-axi4lite_Termination_Subordinate-001'> REQ_axi4lite_Termination_Subordinate_001 {
        doc /* OKF: docs/modules/bus/axi4lite/axi4lite_Termination_Subordinate.md#REQ-axi4lite_Termination_Subordinate-001 */
    }

    requirement def <'REQ-axi4stream_DeMux-001'> REQ_axi4stream_DeMux_001 {
        doc /* OKF: docs/modules/bus/axi4stream/axi4stream_DeMux.md#REQ-axi4stream_DeMux-001 */
    }

    requirement def <'REQ-axi4stream_FIFO_CDC-001'> REQ_axi4stream_FIFO_CDC_001 {
        doc /* OKF: docs/modules/bus/axi4stream/axi4stream_FIFO_CDC.md#REQ-axi4stream_FIFO_CDC-001 */
    }

    requirement def <'REQ-axi4stream_FIFO_TempGot-001'> REQ_axi4stream_FIFO_TempGot_001 {
        doc /* OKF: docs/modules/bus/axi4stream/axi4stream_FIFO_TempGot.md#REQ-axi4stream_FIFO_TempGot-001 */
    }

    requirement def <'REQ-axi4stream_FIFO_TempPut-001'> REQ_axi4stream_FIFO_TempPut_001 {
        doc /* OKF: docs/modules/bus/axi4stream/axi4stream_FIFO_TempPut.md#REQ-axi4stream_FIFO_TempPut-001 */
    }

    requirement def <'REQ-axi4stream_FIFO-001'> REQ_axi4stream_FIFO_001 {
        doc /* OKF: docs/modules/bus/axi4stream/axi4stream_FIFO.md#REQ-axi4stream_FIFO-001 */
    }

    requirement def <'REQ-axi4stream_Mux-001'> REQ_axi4stream_Mux_001 {
        doc /* OKF: docs/modules/bus/axi4stream/axi4stream_Mux.md#REQ-axi4stream_Mux-001 */
    }

    requirement def <'REQ-axi4stream_Mux-002'> REQ_axi4stream_Mux_002 {
        doc /* OKF: docs/modules/bus/axi4stream/axi4stream_Mux.md#REQ-axi4stream_Mux-002 */
    }

    requirement def <'REQ-axi4stream_Pause-001'> REQ_axi4stream_Pause_001 {
        doc /* OKF: docs/modules/bus/axi4stream/axi4stream_Pause.md#REQ-axi4stream_Pause-001 */
    }

    requirement def <'REQ-axi4stream_Stage-001'> REQ_axi4stream_Stage_001 {
        doc /* OKF: docs/modules/bus/axi4stream/axi4stream_Stage.md#REQ-axi4stream_Stage-001 */
    }

    requirement def <'REQ-axi4stream_Stage-002'> REQ_axi4stream_Stage_002 {
        doc /* OKF: docs/modules/bus/axi4stream/axi4stream_Stage.md#REQ-axi4stream_Stage-002 */
    }

    requirement def <'REQ-axi4stream_Termination_Receiver-001'> REQ_axi4stream_Termination_Receiver_001 {
        doc /* OKF: docs/modules/bus/axi4stream/axi4stream_Termination_Receiver.md#REQ-axi4stream_Termination_Receiver-001 */
    }

    requirement def <'REQ-axi4stream_Termination_Transmitter-001'> REQ_axi4stream_Termination_Transmitter_001 {
        doc /* OKF: docs/modules/bus/axi4stream/axi4stream_Termination_Transmitter.md#REQ-axi4stream_Termination_Transmitter-001 */
    }

    requirement def <'REQ-bus_Arbiter-001'> REQ_bus_Arbiter_001 {
        doc /* OKF: docs/modules/bus/bus_Arbiter.md#REQ-bus_Arbiter-001 */
    }

    requirement def <'REQ-bus_Arbiter-002'> REQ_bus_Arbiter_002 {
        doc /* OKF: docs/modules/bus/bus_Arbiter.md#REQ-bus_Arbiter-002 */
    }

}
